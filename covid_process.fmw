FME workspace covid_process.fmw

Parameters:
- SourceDataset_CSV2 = $(FME_MF_DIR)csse_covid_19_data/csse_covid_19_time_series/time_series_19-covid-Confirmed.csv   # Source CSV (Comma Separated Value) File(s)
- SourceDataset_CSV2_5 = $(FME_MF_DIR)csse_covid_19_data/csse_covid_19_time_series/time_series_19-covid-Deaths.csv   # Source CSV (Comma Separated Value) File(s)
- SourceDataset_CSV2_4 = $(FME_MF_DIR)csse_covid_19_data/csse_covid_19_time_series/time_series_19-covid-Recovered.csv   # Source CSV (Comma Separated Value) File(s)
- DestDataset_CSV2 = $(FME_MF_DIR)csse_covid_19_data/csse_covid_19_time_series   # Destination CSV (Comma Separated Value) Folder

Readers:
- CSV2_1: CSV2 from $(SourceDataset_CSV2)
- CSV2_2: CSV2 from $(SourceDataset_CSV2_5)
- CSV2_3: CSV2 from $(SourceDataset_CSV2_4)

Writers:
- CSV2_4: CSV2 to $(DestDataset_CSV2)

Note: CSV: time_series_19-covid-Recovered [CSV2]
CSV (reader CSV2_3)
    attributes: Province/State string, Country/Region string, Lat string, Long string, 1/22/20 string, 1/23/20 string, 1/24/20 string, 1/25/20 string, 1/26/20 string, 1/27/20 string, 1/28/20 string, 1/29/20 string, 1/30/20 string, 1/31/20 string, 2/1/20 string, 2/2/20 string, 2/3/20 string, 2/4/20 string, 2/5/20 string, 2/6/20 string, 2/7/20 string, 2/8/20 string, 2/9/20 string, 2/10/20 string, 2/11/20 string, 2/12/20 string, 2/13/20 string, 2/14/20 string, 2/15/20 string, 2/16/20 string,
      2/17/20 string, 2/18/20 string, 2/19/20 string, 2/20/20 string, 2/21/20 string, 2/22/20 string, 2/23/20 string, 2/24/20 string, 2/25/20 string, 2/26/20 string, 2/27/20 string, 2/28/20 string, 2/29/20 string, 3/1/20 string, 3/2/20 string, 3/3/20 string, 3/4/20 string, 3/5/20 string, 3/6/20 string, 3/7/20 string
    -> CSV_3
    -> AttributeManager_2
CSV_3: Inspector
AttributeManager_2
    ATTR_TABLE = SET_TO TYPE = RECOVERED
    -> AttributeManager
Note: CSV: time_series_19-covid-Deaths [CSV2]
CSV (reader CSV2_2)
    attributes: Province/State string, Country/Region string, Lat string, Long string, 1/22/20 string, 1/23/20 string, 1/24/20 string, 1/25/20 string, 1/26/20 string, 1/27/20 string, 1/28/20 string, 1/29/20 string, 1/30/20 string, 1/31/20 string, 2/1/20 string, 2/2/20 string, 2/3/20 string, 2/4/20 string, 2/5/20 string, 2/6/20 string, 2/7/20 string, 2/8/20 string, 2/9/20 string, 2/10/20 string, 2/11/20 string, 2/12/20 string, 2/13/20 string, 2/14/20 string, 2/15/20 string, 2/16/20 string,
      2/17/20 string, 2/18/20 string, 2/19/20 string, 2/20/20 string, 2/21/20 string, 2/22/20 string, 2/23/20 string, 2/24/20 string, 2/25/20 string, 2/26/20 string, 2/27/20 string, 2/28/20 string, 2/29/20 string, 3/1/20 string, 3/2/20 string, 3/3/20 string, 3/4/20 string, 3/5/20 string, 3/6/20 string, 3/7/20 string
    -> CSV_2
    -> AttributeManager_3
AttributeManager_3
    ATTR_TABLE = SET_TO TYPE = DEATH
    -> AttributeManager
CSV_2: Inspector
Note: CSV: time_series_19-covid-Confirmed [CSV2]
CSV (reader CSV2_1)
    attributes: Province/State string, Country/Region string, Lat string, Long string, 1/22/20 string, 1/23/20 string, 1/24/20 string, 1/25/20 string, 1/26/20 string, 1/27/20 string, 1/28/20 string, 1/29/20 string, 1/30/20 string, 1/31/20 string, 2/1/20 string, 2/2/20 string, 2/3/20 string, 2/4/20 string, 2/5/20 string, 2/6/20 string, 2/7/20 string, 2/8/20 string, 2/9/20 string, 2/10/20 string, 2/11/20 string, 2/12/20 string, 2/13/20 string, 2/14/20 string, 2/15/20 string, 2/16/20 string,
      2/17/20 string, 2/18/20 string, 2/19/20 string, 2/20/20 string, 2/21/20 string, 2/22/20 string, 2/23/20 string, 2/24/20 string, 2/25/20 string, 2/26/20 string, 2/27/20 string, 2/28/20 string, 2/29/20 string, 3/1/20 string, 3/2/20 string, 3/3/20 string, 3/4/20 string, 3/5/20 string, 3/6/20 string, 3/7/20 string
    -> CSV
    -> AttributeManager_4
CSV: Inspector
AttributeManager_4
    ATTR_TABLE = SET_TO TYPE = CONFIRMED
    -> AttributeManager
AttributeManager
    ATTR_TABLE = SET_TO Province/State = FME_CONDITIONAL:DEFAULT_VALUE'_FME_NO_OP_'BOOL_OP;OR;COMPOSITE_TEST;1;TEST Province/State ATTRIBUTE_IS_EMPTY _FME_BLANK_STRING_'@Value(Country/Region)_OTHERS'FME_NUM_CONDITIONS2___
    -> AttributeTrimmer
AttributeTrimmer
    SRC_ATTRS = 2/5/20,2/10/20,Country/Region,2/18/20,2/14/20,2/22/20,2/11/20,2/27/20,2/19/20,2/28/20,1/27/20,TYPE,2/24/20,3/7/20,2/15/20,3/1/20,2/7/20,2/20/20,3/6/20,Province/State,1/28/20,2/1/20,2/23/20,2/17/20,2/29/20,1/25/20,2/3/20,1/29/20,3/2/20,2/6/20,2/4/20,1/23/20,3/4/20,2/25/20,1/26/20,3/3/20,Lat,1/24/20,1/31/20,2/13/20,2/8/20,2/12/20,3/5/20,1/22/20,Long,2/21/20,1/30/20,2/9/20,2/2/20,2/16/20,2/26/20
    TRIM_TO_NONE = Yes
    TRIM_TYPE = Both
    -> Sorter
Sorter
    SORT_PARM = Country/Region ALPHA ASCENDING Province/State ALPHA ASCENDING TYPE ALPHA ASCENDING
    SORTED -> StringCaseChanger
StringCaseChanger
    ATTRCHOICE = All Attributes
    CHANGE_TYPE = UPPERCASE
    -> time_series_19-covid-merge (writer CSV2_4)
    -> AttributeManager_Output
AttributeManager_Output: Inspector
time_series_19-covid-merge (writer CSV2_4)
    attributes: TYPE string, Province/State string, Country/Region string, Lat string, Long string, 1/22/20 string, 1/23/20 string, 1/24/20 string, 1/25/20 string, 1/26/20 string, 1/27/20 string, 1/28/20 string, 1/29/20 string, 1/30/20 string, 1/31/20 string, 2/1/20 string, 2/2/20 string, 2/3/20 string, 2/4/20 string, 2/5/20 string, 2/6/20 string, 2/7/20 string, 2/8/20 string, 2/9/20 string, 2/10/20 string, 2/11/20 string, 2/12/20 string, 2/13/20 string, 2/14/20 string, 2/15/20 string,
      2/16/20 string, 2/17/20 string, 2/18/20 string, 2/19/20 string, 2/20/20 string, 2/21/20 string, 2/22/20 string, 2/23/20 string, 2/24/20 string, 2/25/20 string, 2/26/20 string, 2/27/20 string, 2/28/20 string, 2/29/20 string, 3/1/20 string, 3/2/20 string, 3/3/20 string, 3/4/20 string, 3/5/20 string, 3/6/20 string, 3/7/20 string
